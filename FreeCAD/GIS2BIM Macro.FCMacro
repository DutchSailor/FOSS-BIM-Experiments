## GIS2BIM Library

## Webserverdata
PDOKServerURL = "http://geodata.nationaalgeoregister.nl/locatieserver/v3/free?wt=json&rows=1&q="

DutchGEOCadasterServerRequest1 = "http://geodata.nationaalgeoregister.nl/kadastralekaart/wfs/v4_0?service=WFS&version=2.0.0&request=GetFeature&typeName=perceel&bbox="
#For curves of Cadastral Parcels

DutchGEOCadasterServerRequest2 = "http://geodata.nationaalgeoregister.nl/kadastralekaart/wfs/v4_0?service=WFS&version=2.0.0&request=GetFeature&typeName=kadastralekaartv4:nummeraanduidingreeks&bbox="
#For 'nummeraanduidingreeks' of Cadastral Parcels

DutchGEOCadasterServerRequest3 = "http://geodata.nationaalgeoregister.nl/kadastralekaart/wfs/v4_0?service=WFS&version=2.0.0&request=GetFeature&typeName=kadastralekaartv4:openbareruimtenaam&bbox="
#For 'openbareruimtenaam' of Cadastral Parcels

DutchGEOBAG = "http://geodata.nationaalgeoregister.nl/bag/wfs/v1_1?service=wfs&version=2.0.0&request=GetFeature&typeName=bag:pand&bbox="
#Building Contour of BAG

DutchGEORuimtelijkeplannenBouwvakServerRequest = "http://afnemers.ruimtelijkeplannen.nl/afnemers/services?&service=WFS&version=1.1.0&request=GetFeature&typeName=app:Bouwvlak&bbox="

xPathCadaster1 = ".//{http://www.opengis.net/gml/3.2}posList"
xPathCadaster2 = ".//{http://www.opengis.net/gml/3.2}pos"
xPathStringsCadastreTextAngle = [".//{http://kadastralekaartv4.geonovum.nl}hoek", ".//{http://kadastralekaartv4.geonovum.nl}tekst"]
xPathRuimtelijkePlannen = ".//{http://www.opengis.net/gml}posList"
#Xpath for several Cadastral Servers



import urllib.request
import xml.etree.ElementTree as ET
import json

def GIS2BIM_GML_poslistData(tree, xPathString,dx,dy,scale,DecimalNumbers):
    posLists = tree.findall(xPathString)
    xyPosList = []
    for posList in posLists:
        dataPosList = posList.text
        coordSplit = dataPosList.split()
        x = 0
        coordSplitXY = []
        for j in range(0, int(len(coordSplit) / 2)):
            xy_coord = (round((float(coordSplit[x])+dx)*scale,DecimalNumbers), round((float(coordSplit[x+1])+dy)*scale,DecimalNumbers))
            coordSplitXY.append(xy_coord)
            x +=2
        xyPosList.append(coordSplitXY)
    return xyPosList

def GIS2BIM_CreateBoundingBox(CoordinateX,CoordinateY,BoxWidth,BoxHeight,DecimalNumbers):
    XLeft = round(CoordinateX-0.5*BoxWidth,DecimalNumbers)
    XRight = round(CoordinateX+0.5*BoxWidth,DecimalNumbers)
    YBottom = round(CoordinateY-0.5*BoxHeight,DecimalNumbers)
    YTop = round(CoordinateY+0.5*BoxHeight,DecimalNumbers)
    boundingBoxString1 = str(XLeft) + "," + str(YBottom) + "," + str(XRight) + "," + str(YTop)
    return boundingBoxString1

def GIS2BIM_GetLocationDataNetherlands(City,Streetname,Housenumber):
    PDOKServer = PDOKServerURL
    requesturl =  PDOKServer + City +"%20and%20" + Streetname + "%20and%20" + Housenumber
    urlFile = urllib.request.urlopen(requesturl)
    jsonList = json.load(urlFile)
    jsonList = jsonList["response"]["docs"]
    jsonList1 = jsonList[0]
    RD = jsonList1['centroide_rd']
    RD = RD.replace("("," ").replace(")"," ")
    RD = RD.split()
    RDx = RD[1]
    RDy = RD[2]
    return RDx,RDy, requesturl

def GIS2BIM_PointsFromWFS(serverName,boundingBoxString,xPathString,dx,dy,scale,DecimalNumbers):
    myrequesturl = serverName + boundingBoxString
    urlFile = urllib.request.urlopen(myrequesturl)
    tree = ET.parse(urlFile)
    xyPosList = GIS2BIM_GML_poslistData(tree,xPathString,dx,dy,scale,DecimalNumbers)
    return xyPosList

def GIS2BIM_DataFromWFS(serverName,boundingBoxString,xPathStringCoord,xPathStrings,dx,dy,scale,DecimalNumbers):
    myrequesturl = serverName + boundingBoxString
    urlFile = urllib.request.urlopen(myrequesturl)
    tree = ET.parse(urlFile)
    xyPosList = GIS2BIM_GML_poslistData(tree,xPathStringCoord,dx,dy,scale,DecimalNumbers)
    xPathResults = []
    for xPathString in xPathStrings:
        a = tree.findall(xPathString)
        xPathResulttemp2 = []
        for xPathResult in a:
            xPathResulttemp2.append(xPathResult.text)
        xPathResults.append(xPathResulttemp2)
    xPathResults.insert(0,xyPosList)
    return xPathResults

a = GIS2BIM_GetLocationDataNetherlands("dordrecht","Lange%20Geldersekade","2")
width = 500
Rdx = float(a[0])
Rdy = float(a[1])
Rdx = 104857.637
Rdy = 425331.936
Bbox = GIS2BIM_CreateBoundingBox(Rdx,Rdy,width,width,2)

curvesCadastralParcels = GIS2BIM_PointsFromWFS(DutchGEOCadasterServerRequest1,Bbox,xPathCadaster1,-Rdx,-Rdy,1000,1)
curvesBuildings = GIS2BIM_PointsFromWFS(DutchGEOBAG,Bbox,xPathCadaster1,-Rdx,-Rdy,1000,1)
curvesRuimtelijkePlannen = GIS2BIM_PointsFromWFS(DutchGEORuimtelijkeplannenBouwvakServerRequest,Bbox,xPathRuimtelijkePlannen,-Rdx,-Rdy,1000,1)
textDataCadastralParcels = GIS2BIM_DataFromWFS(DutchGEOCadasterServerRequest2,Bbox,xPathCadaster2,xPathStringsCadastreTextAngle,-Rdx,-Rdy,1000,1)
textDataOpenbareRuimtenaam = GIS2BIM_DataFromWFS(DutchGEOCadasterServerRequest3,Bbox,xPathCadaster2,xPathStringsCadastreTextAngle,-Rdx,-Rdy,1000,1)

import Draft

for i in curvesRuimtelijkePlannen:
	pointlist = []
	for j in i:
		pointlist.append(FreeCAD.Vector(j[0], j[1], 0))
	a = Draft.makeWire(pointlist, closed=True)
	
FreeCAD.ActiveDocument.recompute()
