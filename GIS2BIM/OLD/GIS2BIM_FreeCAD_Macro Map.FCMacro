####imports
import PySide
from PySide2.QtWebEngineWidgets import QWebEngineView
from PySide2.QtWebEngineWidgets import QWebEnginePage 
from PySide2 import  QtUiTools, QtNetwork,QtCore, QtGui, QtWidgets, QtWebChannel
from PySide2.QtCore import QUrl
import functools
import requests
import sys,os
import GIS2BIM
import GIS2BIM_FreeCAD
import GIS2BIM_CRS 
import time
import re

sys.path.append(os.path.join(sys.path[0]))

SiteName = "GIS2BIM-Sitedata"
TempFolderName = "GIStemp/"
Lat = str(GIS2BIM_FreeCAD.ArchSiteCreateCheck(SiteName).WGS84_Latitude)
Long = str(GIS2BIM_FreeCAD.ArchSiteCreateCheck(SiteName).WGS84_Longitude)
BoundingboxWidth = str(GIS2BIM_FreeCAD.ArchSiteCreateCheck(SiteName).BoundingboxWidth)
BoundingboxHeight = str(GIS2BIM_FreeCAD.ArchSiteCreateCheck(SiteName).BoundingboxHeight)

#Create temp folders/files
URL = GIS2BIM.GetWebServerData("HTMLLocationData", "Other", "URL")
#filepathBaseMap = GIS2BIM.DownloadURL(GIS2BIM_FreeCAD.CreateTempFolder(TempFolderName),URL,"basemap.html")
filepathNewMap = GIS2BIM.DownloadURL(GIS2BIM_FreeCAD.CreateTempFolder(TempFolderName),URL,"map.html")
filepathBaseMap = "C:/Users/mikev/OneDrive/Bureaublad/TEMP/GIStemp/basemap.html"	
tempFolderPath = GIS2BIM_FreeCAD.CreateTempFolder(TempFolderName)	
temptxtPath = tempFolderPath + "/temp.txt"
JSFile = "C:/TEMP/JSmap.js"

for file in os.listdir(tempFolderPath): # Cleanup of txt-files
	if file.endswith(".txt"):
		filename = tempFolderPath + "/" + file
		os.remove(filename)

class GISLocation_Dialog(QtWidgets.QDialog):

	def __init__(self):
		super(GISLocation_Dialog, self).__init__()
		self.initUI()

	def initUI(self):
		self.result = userCancelled
		self.setWindowTitle("Set Geographic Location")
		self.setGeometry(100, 100, 920, 900)

		# CrossLines
		self.pen = QtGui.QPen(QtCore.Qt.black, 50, QtCore.Qt.SolidLine)
		self.painter = QtGui.QPainter(self)
		self.painter.setPen(self.pen)
		self.x01 = 510
		self.y0 = 50
		self.y1 = 870
		self.x2 = 50
		self.y2 = 1485
		self.x3 = 920
		self.point1vert = QtCore.QPointF(self.x01,self.y0)
		self.point2vert = QtCore.QPointF(self.x01,self.y1) 
		self.point1hor = QtCore.QPointF(self.x2,self.y2)
		self.point2hor = QtCore.QPointF(self.x3,self.y2) 
		self.line1 = QtCore.QLineF(self.point1vert, self.point2vert)
		self.line2 = QtCore.QLineF(self.point1hor, self.point2hor)
		self.painter.drawPoint(self.point1vert)
		self.painter.drawLine(self.line1)
		self.painter.drawLine(self.line2)

		self.centralwidget = QtWidgets.QWidget(self)
		self.centralwidget.setObjectName("map")

		self.webView = QWebEngineView(self.centralwidget)
		self.webView.setGeometry(QtCore.QRect(40, 40, 840, 620))
		self.webPage = QWebEnginePage()
		
		#Download map.html from GIS2BIM Repository and set projectlocation
		os.remove(filepathNewMap)
		BaseMap = open(filepathBaseMap,"r")
		BaseMapstr = BaseMap.read()
		Newstr = BaseMapstr.replace("51LAT",str(Lat))
		Newstr = Newstr.replace("4LONG", str(Long))
		Newstr = Newstr.replace("FOLDERNAME", temptxtPath)
		Newstr = Newstr.replace("WBBOX",BoundingboxWidth)
		Newstr = Newstr.replace("HBBOX",BoundingboxHeight)
		f1 = open(filepathNewMap, "x")
		f1 = open(filepathNewMap, "w")
		f1.write(Newstr)
		f1.close()

		#Load map.html		
		self.webPage.load(QUrl(QtCore.QUrl(filepathNewMap)))
		self.webView.setPage(self.webPage)

		lat = Lat
		lon = Long
		self.lat = Lat
		self.lon = Long

		QtCore.QMetaObject.connectSlotsByName(self)
		self.label1 = QtWidgets.QLabel("Click on the map to set the center of the boundingbox" , self)
		self.label1.move(50, 25)

		#Search 
		self.label3 = QtWidgets.QLabel("Search Place/Address", self)
		self.label3.move(40, 675)

		#search line
		self.searchline1 = QtWidgets.QPlainTextEdit(self)
		self.searchline1.insertPlainText("Dordrecht")
		self.searchline1.setFixedWidth(400)
		self.searchline1.setFixedHeight(30)
		self.searchline1.move(195, 670)

		# search button
		searchButton = QtWidgets.QPushButton('Search', self)
		searchButton.clicked.connect(self.onSearch)
		searchButton.setAutoDefault(True)
		searchButton.move(600, 670)

		#list of CRS
		self.dropdownCRSlabel = QtWidgets.QLabel("Coordinate Reference System", self)
		self.dropdownCRSlabel.move(40, 735)
		#
		self.dropdownCRS = QtWidgets.QComboBox(self)
		self.dropdownCRS.addItems(GIS2BIM_CRS.inputChars)
		self.dropdownCRS.setCurrentText("28992")
		self.dropdownCRS.setFixedWidth(300)
		self.dropdownCRS.move(200, 730)
		CRS_EPSG_SRID = GIS2BIM_CRS.inputChars[self.dropdownCRS.currentIndex()]
		CRS_EPSG_Description = GIS2BIM_CRS.getCRSdata(CRS_EPSG_SRID)		
		self.dropdownCRSlabel = QtWidgets.QLabel(CRS_EPSG_Description, self)
		self.dropdownCRSlabel.move(350, 735)

		# boundingbox width
		self.boundingboxwidth = QtWidgets.QLineEdit(self)
		self.boundingboxwidth.setInputMask("")
		self.boundingboxwidth.setText(BoundingboxWidth)
		self.boundingboxwidth.setFixedWidth(100)
		self.boundingboxwidth.move(200, 760)
		self.boundingboxwidth.editingFinished.connect(self.onboundingboxwidth)
		self.label1 = QtWidgets.QLabel("Boundingbox Width [m]", self)
		self.label1.move(40, 765)


		# boundingbox height
		self.boundingboxheight = QtWidgets.QLineEdit(self)
		self.boundingboxheight.setInputMask("")
		self.boundingboxheight.setText(BoundingboxHeight)
		self.boundingboxheight.setFixedWidth(100)
		self.boundingboxheight.move(200, 790)
		self.boundingboxheight.editingFinished.connect(self.onboundingboxheight)
		self.label2 = QtWidgets.QLabel("Boundingbox Height [m]", self)
		self.label2.move(40, 795)

		# cancel button
		cancelButton = QtWidgets.QPushButton('Cancel', self)
		cancelButton.clicked.connect(self.onCancel)
		cancelButton.setAutoDefault(True)
		cancelButton.move(120, 840)
		# OK button
		okButton = QtWidgets.QPushButton('OK', self)
		okButton.clicked.connect(self.onOk)
		okButton.move(35, 840)
		self.show()
	def onboundingboxwidth(self):
		JSFile2 = "C:/Users/mikev/OneDrive/Documenten/GitHub/GIS2BIM/datafiles/mapJSbboxUpdate.js"
		JS2 = open(JSFile2,"r")
		JS2 = JS2.read()
		JS2 = JS2.replace("WBBOX", self.boundingboxwidth.text())
		JS2 = JS2.replace("HBBOX", self.boundingboxheight.text())
		self.webPage.runJavaScript(JS2) # update boundingboxwidth in mapview

	def onboundingboxheight(self):
		JSFile2 = "C:/Users/mikev/OneDrive/Documenten/GitHub/GIS2BIM/datafiles/mapJSbboxUpdate.js"
		JS3 = open(JSFile2,"r")
		JS3 = JS3.read()
		JS3 = JS3.replace("WBBOX", self.boundingboxwidth.text())
		JS3 = JS3.replace("HBBOX", self.boundingboxheight.text())
		self.webPage.runJavaScript(JS3) # update boundingboxheight in mapview

	def onCancel(self):
		self.result= userCancelled
		self.close()

	def onSearch(self):	
		#self.result= userOK
		searchterm = self.searchline1.toPlainText().split()
		
		lat = (GIS2BIM.GIS2BIM_NominatimAPI(searchterm))[0]
		lon = (GIS2BIM.GIS2BIM_NominatimAPI(searchterm))[1]
		JS = open(JSFile,"r")
		JS = JS.read()
		JS = JS.replace("51LAT",str(lat))
		JS = JS.replace("4LONG", str(lon))
		JS = JS.replace("FOLDERNAME", temptxtPath)
		self.webPage.runJavaScript(JS) # set view

	def onOk(self):
		# Find latest version of temp.txt which contains the chosen coordinates
		filenames = []
		filestamps = []
		for filename in os.listdir(tempFolderPath):
			if filename.endswith(".txt"):
				filenames.append(filename)
				i = os.path.getmtime(tempFolderPath + "/" + filename)
				filestamps.append(time.strftime('%Y-%m-%d %H:%M:%S', time.localtime(i)))
		latest = max(filestamps)
		indexof = filestamps.index(latest)
		latestfile = filenames[indexof]
		filepathTempfileLATLONData = tempFolderPath + "/" + latestfile #most recent file
	
		tempFileCoordinates = open(filepathTempfileLATLONData,"r")
		CoordinatesString = tempFileCoordinates.read()
		tempFileCoordinates.close()

		strsplit = re.split("[(, )]", CoordinatesString)
		self.lat = strsplit[1]
		self.lon = strsplit[3]		
		self.result= userOK
		self.close()
		
	def panMap(self, lng, lat):
		frame = self.webView.page().mainFrame()
		frame.evaluateJavaScript('map.panTo(L.latLng({}, {}));'.format(lat, lng))


	def onLoadFinished(self):
		with open('map.js', 'r') as f:
			frame = self.view.page().mainFrame()
			frame.evaluateJavaScript(f.read())
	
# Constant definitions
userCancelled		= "Cancelled"
userOK			= "OK"

form = GISLocation_Dialog()
form.exec_()

if form.result==userOK:
	SiteName = "GIS2BIM-Sitedata"
	SiteObject = GIS2BIM_FreeCAD.ArchSiteCreateCheck(SiteName)
	CRS_EPSG_SRID = SiteObject.CRS_EPSG_SRID = GIS2BIM_CRS.inputChars[form.dropdownCRS.currentIndex()]
	SiteObject.WGS84_Longitude = form.lon
	SiteObject.WGS84_Latitude = form.lat
	Transformation = GIS2BIM.TransformCRS_epsg("4326",CRS_EPSG_SRID,form.lon,form.lat)
	SiteObject.CRS_x = float(Transformation[0])
	SiteObject.CRS_y = float(Transformation[1])
	SiteObject.BoundingboxWidth = float(form.boundingboxwidth.text())
	SiteObject.BoundingboxHeight = float(form.boundingboxheight.text())
	SiteObject.CRS_EPSG_Description = GIS2BIM_CRS.getCRSdata(CRS_EPSG_SRID)
