from PySide2 import QtCore, QtWidgets
from PySide2.QtGui import*

import FreeCAD

import GIS2BIM
import GIS2BIM_FreeCAD

import urllib
import urllib.request
import xml.etree.ElementTree as ET
import json
import math
import re
from PIL import Image

URL = "https://c.tile.osm.org/17/67920/42545.png"

opener=urllib.request.build_opener()
opener.addheaders=[('User-Agent','Mozilla/5.0 (Windows NT 6.1; WOW64) AppleWebKit/537.36 (KHTML, like Gecko) Chrome/36.0.1941.0 Safari/537.36')]
urllib.request.install_opener(opener)

local=''

#file = urllib.request.urlretrieve(URL,"test9.jpg")

#img = Image.open("test9.jpg")
img = Image.open(urllib.request.urlopen(URL))

print(img)


	def createPushButtonGroup(self):
		groupBox = QtWidgets.QGroupBox("&Push Buttons")
		groupBox.setCheckable(True)
		groupBox.setChecked(True)
		
		pushButton = QtWidgets.QPushButton("&Normal Button")
		toggleButton = QtWidgets.QPushButton("&Toggle Button")
		toggleButton.setCheckable(True)
		toggleButton.setChecked(True)
		flatButton = QtWidgets.QPushButton("&Flat Button")
		flatButton.setFlat(True)
		
		popupButton = QtWidgets.QPushButton("Pop&up Button")
		menu = QtWidgets.QMenu(self)
		menu.addAction("&First Item")
		menu.addAction("&Second Item")
		menu.addAction("&Third Item")
		menu.addAction("F&ourth Item")
		popupButton.setMenu(menu)
		
		newAction = menu.addAction("Submenu")
		subMenu = QtWidgets.QMenu("Popup Submenu", self)
		subMenu.addAction("Item 1")
		subMenu.addAction("Item 2")
		subMenu.addAction("Item 3")
		newAction.setMenu(subMenu)
		
		vbox = QtWidgets.QVBoxLayout()
		vbox.addWidget(pushButton)
		vbox.addWidget(toggleButton)
		vbox.addWidget(flatButton)
		vbox.addWidget(popupButton)
		vbox.addStretch(1)
		groupBox.setLayout(vbox)
		#	groupBox.show()
		return groupBox
