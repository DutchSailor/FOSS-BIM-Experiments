# WMS Importer

import sys
sys.path.insert(1, 'C:/Users/mikev/OneDrive/Documenten/GitHub/FOSS-BIM-Experiments/GIS2BIM')

import urllib.request
import urllib
import xml.etree.ElementTree as ET
import json
import Draft
import Part

import GIS2BIM
import GIS2BIM_FreeCAD
import GIS2BIM_NL

import PySide2
from PySide2 import QtCore, QtGui, QtWidgets

####import for WebPage
from PySide2.QtWebEngineWidgets import QWebEngineView
from PySide2 import  QtUiTools, QtNetwork
from PySide2.QtCore import QUrl
import functools

class GISWMS_Dialog(QtWidgets.QDialog):

	def __init__(self):
		super(GISWMS_Dialog, self).__init__()
		self.initUI()

	def initUI(self):
		self.result = userCancelled
		self.setWindowTitle("Load Raster Data with WMS(Web Map Server)")
		self.setGeometry(100, 100, 920, 920)
 
		# frame for image example in webpage
		self.centralwidget = QtWidgets.QWidget(self)
		self.centralwidget.setObjectName("image")
		self.webView = QWebEngineView(self.centralwidget)
		self.webView.setGeometry(QtCore.QRect(40, 40, 800, 620))

		self.webView.setUrl(QtCore.QUrl("C:/Users/mikev/OneDrive/Documenten/GitHub/FOSS-BIM-Experiments/GIS2BIM/image.html")) # url your question
		self.webView.setObjectName("webView")

		# webservernameAndRequest
		self.webserverName1 = QtWidgets.QPlainTextEdit(self)
		self.webserverName1.insertPlainText("http://geodata.nationaalgeoregister.nl/luchtfoto/rgb/wms?&request=GetMap&VERSION=1.3.0&STYLES=&layers=2019_ortho25&width=3000&height=3000&format=image/png&crs=EPSG:28992&bbox=")
		self.webserverName1.setFixedWidth(300)
		self.webserverName1.move(500, 600)
		self.label1 = QtWidgets.QLabel("Webserveraddress & Request", self)
		self.label1.move(350, 610)
		self.label1a = QtWidgets.QLabel("(ithout boundingboxstring)", self)
		self.label1a.move(350, 640)


		#X-coordinate
		self.numericInput1X = QtWidgets.QLineEdit(self)
		self.numericInput1X.setInputMask("")
		self.numericInput1X.setText("102857.637")
		self.numericInput1X.setFixedWidth(100)
		self.numericInput1X.move(200, 600)
		self.label2 = QtWidgets.QLabel("X-coordinate", self)
		self.label2.move(20, 600)
		
		#Y-coordinate		
		self.numericInput2Y = QtWidgets.QLineEdit(self)
		self.numericInput2Y.setInputMask("")
		self.numericInput2Y.setText("425331.936")
		self.numericInput2Y.setFixedWidth(100)
		self.numericInput2Y.move(200, 630)
		self.label3 = QtWidgets.QLabel("Y-coordinate", self)
		self.label3.move(20, 630)
		
		# boundingbox width
		self.boundingboxwidth = QtWidgets.QLineEdit(self)
		self.boundingboxwidth.setInputMask("")
		self.boundingboxwidth.setText("500")
		self.boundingboxwidth.setFixedWidth(100)
		self.boundingboxwidth.move(200, 660)
		self.label4 = QtWidgets.QLabel("Boundingbox Width [m]", self)
		self.label4.move(20, 660)

		# boundingbox height
		self.boundingboxheight = QtWidgets.QLineEdit(self)
		self.boundingboxheight.setInputMask("")
		self.boundingboxheight.setText("500")
		self.boundingboxheight.setFixedWidth(100)
		self.boundingboxheight.move(200, 690)
		self.label5 = QtWidgets.QLabel("Boundingbox Height [m]", self)
		self.label5.move(20, 690)

		# dx 
		self.dx = QtWidgets.QLineEdit(self)
		self.dx.setInputMask("")
		self.dx.setText("0")
		self.dx.setFixedWidth(100)
		self.dx.move(200, 720)
		self.label6 = QtWidgets.QLabel("dx placement [m]", self)
		self.label6.move(20, 720)

		# dy 
		self.dy = QtWidgets.QLineEdit(self)
		self.dy.setInputMask("")
		self.dy.setText("0")
		self.dy.setFixedWidth(100)
		self.dy.move(200, 750)
		self.label7 = QtWidgets.QLabel("dy placement [m]", self)
		self.label7.move(20, 750)

		# filelocation
		self.filelocation = QtWidgets.QLineEdit(self)
		self.filelocation.setInputMask("")
		self.filelocation.setText("C:/TEMP/test.jpg")
		self.filelocation.setFixedWidth(100)
		self.filelocation.move(200, 780)
		self.label8 = QtWidgets.QLabel("temporary filelocation", self)
		self.label8.move(20, 780)

		# test WMS button
		testWMSButton = QtWidgets.QPushButton('test WMS', self)
		testWMSButton.clicked.connect(self.testWMS)
		testWMSButton.move(200, 870)

		# cancel button
		cancelButton = QtWidgets.QPushButton('Cancel', self)
		cancelButton.clicked.connect(self.onCancel)
		cancelButton.setAutoDefault(True)
		cancelButton.move(100, 870)

		# Ok WMS button
		okButton = QtWidgets.QPushButton('OK', self)
		okButton.clicked.connect(self.onOk)
		okButton.move(20, 870)
		self.show()

	def onCancel(self):
		self.result= userCancelled
		self.close()

	def testWMS(self):
		self.result	= userTest

	def onOk(self):
		self.result	= userOK
		self.close()

# Constant definitions
userCancelled = "Cancelled"
userOK = "OK"
userTest = "TestWMS"

form = GISWMS_Dialog()
form.exec_()

if form.result==userCancelled:
	pass # steps to handle user clicking Cancel
if form.result==userOK:
	URL = str(form.webserverName1.toPlainText())
	X = float(form.numericInput1X.text())
	Y = float(form.numericInput2Y.text())
	dx = float(form.dx.text())
	dy = float(form.dy.text())
	width = float(form.boundingboxwidth.text())
	height = float(form.boundingboxheight.text())
	fileLocationWMS = str(form.filelocation.text())
	GIS2BIM.CreateBoundingBox(X,Y,width,height,2)
	GIS2BIM.WMSRequest(URL,Bbox,fileLocationWMS)
	ImageAerialPhoto = GIS2BIM_FreeCAD.ImportImage(fileLocationWMS,width,height,1000,"luchtfoto2019")

if form.result==userTest:
	pass # steps to handle user clicking Cancel

FreeCAD.ActiveDocument.recompute()
