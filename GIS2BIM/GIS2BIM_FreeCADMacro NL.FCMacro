# -*- coding: utf8 -*-
#***************************************************************************
#*   Copyright (c) 2021 Maarten Vroegindeweij <maarten@3bm.co.nl>              *
#*                                                                         *
#*   This program is free software; you can redistribute it and/or modify  *
#*   it under the terms of the GNU Lesser General Public License (LGPL)    *
#*   as published by the Free Software Foundation; either version 2 of     *
#*   the License, or (at your option) any later version.                   *
#*   for detail see the LICENCE text file.                                 *
#*                                                                         *
#*   This program is distributed in the hope that it will be useful,       *
#*   but WITHOUT ANY WARRANTY; without even the implied warranty of        *
#*   MERCHANTABILITY or FITNESS FOR A PARTICULAR PURPOSE.  See the         *
#*   GNU Library General Public License for more details.                  *
#*                                                                         *
#*   You should have received a copy of the GNU Library General Public     *
#*   License along with this program; if not, write to the Free Software   *
#*   Foundation, Inc., 59 Temple Place, Suite 330, Boston, MA  02111-1307  *
#*   USA                                                                   *
#*                                                                         *
#***************************************************************************

"""This module provides tools to load GIS information
"""

__title__= "FreeCAD GIS"
__author__ = "Maarten Vroegindeweij"
__url__ = "https://www.freecadweb.org"


## GIS2BIM Library

#import statements
import sys
sys.path.insert(1, 'C:/Users/mikev/OneDrive/Documenten/GitHub/FOSS-BIM-Experiments/GIS2BIM')

import urllib.request
import urllib
import xml.etree.ElementTree as ET
import json
import Draft
import Part

import GIS2BIM
import GIS2BIM_FreeCAD
import GIS2BIM_NL
from PySide import QtGui, QtCore

# UI Class definitions

class GIS2BIM_Dialog(QtGui.QDialog):
	""""""
	def __init__(self):
		super(GIS2BIM_Dialog, self).__init__()
		self.initUI()
	def initUI(self):
		self.result = userCancelled
		# create our window
		# define window		xLoc,yLoc,xDim,yDim
		self.setGeometry(250, 250, 400, 400)
		self.setWindowTitle("Load GIS-data PDOK Netherlands")
		self.setWindowFlags(QtCore.Qt.WindowStaysOnTopHint)
		# create some Labels
		self.label1 = QtGui.QLabel("Rdx(EPSG 28992)", self)
		self.label1.move(20, 20)
		#
		self.numericInput1Rdx = QtGui.QLineEdit(self)
		self.numericInput1Rdx.setInputMask("")
		self.numericInput1Rdx.setText("102857.637")
		self.numericInput1Rdx.setFixedWidth(100)
		self.numericInput1Rdx.move(250, 20)
		#
		self.label2 = QtGui.QLabel("Rdy(EPSG 28992)", self)
		self.label2.move(20, 50)
		#
		self.numericInput2Rdy = QtGui.QLineEdit(self)
		self.numericInput2Rdy.setInputMask("")
		self.numericInput2Rdy.setText("425331.936")
		self.numericInput2Rdy.setFixedWidth(100)
		self.numericInput2Rdy.move(250, 50)
		#
		self.label3 = QtGui.QLabel("Boundingbox Width(m)", self)
		self.label3.move(20, 80)
		#
		self.numericInput3Width = QtGui.QLineEdit(self)
		self.numericInput3Width.setInputMask("")
		self.numericInput3Width.setText("500")
		self.numericInput3Width.setFixedWidth(100)
		self.numericInput3Width.move(250, 80)
		#
		self.label4 = QtGui.QLabel("Boundingbox Height(m)", self)
		self.label4.move(20, 110)
		#
		self.numericInput4Height = QtGui.QLineEdit(self)
		self.numericInput4Height.setInputMask("")
		self.numericInput4Height.setText("500")
		self.numericInput4Height.setFixedWidth(100)
		self.numericInput4Height.move(250, 110)
		# checkboxes
		self.checkbox1 = QtGui.QCheckBox("Cadastral Parcels 2D", self)
		self.checkbox1.move(20,140)
		#
		self.checkbox2 = QtGui.QCheckBox("Building Outline 2D", self)
		self.checkbox2.move(20,170)
		#
		self.checkbox3 = QtGui.QCheckBox("3D Buildings", self)
		self.checkbox3.move(20,200)
		#
		self.checkbox4 = QtGui.QCheckBox("2D Aerialphoto", self)
		self.checkbox4.move(20,230)
		#
		self.checkbox5 = QtGui.QCheckBox("GIS 2D Annotation", self)
		self.checkbox5.move(20,260)
		#
		self.checkbox6 = QtGui.QCheckBox("2D Bestemmingsplan Bouwvlak Vector", self)
		self.checkbox6.move(20,290)
		#
		# cancel button
		cancelButton = QtGui.QPushButton('Cancel', self)
		cancelButton.clicked.connect(self.onCancel)
		cancelButton.setAutoDefault(True)
		cancelButton.move(100, 330)
		# OK button
		okButton = QtGui.QPushButton('OK', self)
		okButton.clicked.connect(self.onOk)
		okButton.move(20, 330)
		# now make the window visible
		self.show()
		#
	def onCancel(self):
		self.result			= userCancelled
		self.close()
	def onOk(self):
		self.result			= userOK
		self.close()

# Class definitions

# Function definitions

# Constant definitions
userCancelled		= "Cancelled"
userOK			= "OK"

# code ***********************************************************************************

form = GIS2BIM_Dialog()
form.exec_()

if form.result==userCancelled:
	pass # steps to handle user clicking Cancel
if form.result==userOK:
	# steps to handle user clicking OK
	Rdx = float(form.numericInput1Rdx.text())
	Rdy = float(form.numericInput2Rdy.text())
	width = float(form.numericInput3Width.text())
	height = float(form.numericInput4Height.text())
	CadastralParcels2D = form.checkbox1.isChecked()
	BuildingOutline2D = form.checkbox2.isChecked()
	Buildings3D = form.checkbox3.isChecked()
	Aerialphoto2D = form.checkbox4.isChecked()
	GIS2DAnnotation = form.checkbox5.isChecked()
	Bestemmingsplan = form.checkbox6.isChecked()

Bbox = GIS2BIM.CreateBoundingBox(Rdx,Rdy,width,height,2)

fileLocationWMS = 'C:\\TEMP\\test9.jpg'

#Create Cadastral Parcels 2D
if CadastralParcels2D is True:
	GIS_2D_Cadastral_Parcel = App.activeDocument().addObject("App::DocumentObjectGroup", "GIS 2D Cadastral Parcel")	
	CadastralParcelCurves = GIS2BIM_FreeCAD.CurvesFromWFS(GIS2BIM_NL.NLPDOKCadastreCadastralParcels,Bbox,GIS2BIM_NL.NLPDOKxPathOpenGISposList,-Rdx,-Rdy,1000,3,2,False,u"Dashdot",(0.0,0.0,0.0))
	GIS_2D_Cadastral_Parcel.addObjects(CadastralParcelCurves)

#Create Building outline 2D
if BuildingOutline2D is True:
	GIS_2D_Building_Outline = App.activeDocument().addObject("App::DocumentObjectGroup", "GIS 2D Building Outline")	
	BAGCurves = GIS2BIM_FreeCAD.CurvesFromWFS(GIS2BIM_NL.NLPDOKBAGBuildingCountour,Bbox,GIS2BIM_NL.NLPDOKxPathOpenGISposList,-Rdx,-Rdy,1000,3,2,True,u"Solid",(0.7,0.0,0.0))
	GIS_2D_Building_Outline.addObjects(BAGCurves)

#Create 3D Building
if Buildings3D is True:
	GIS_3D = App.activeDocument().addObject("App::DocumentObjectGroup", "GIS 3D")	
	curves3DBAG = GIS2BIM.PointsFromWFS(GIS2BIM_NL.NLTUDelftBAG3DV1,Bbox,GIS2BIM_NL.NLPDOKxPathOpenGISPosList2,-Rdx,-Rdy,1000,3,3)
	heightData3DBAG = GIS2BIM.DataFromWFS(GIS2BIM_NL.NLTUDelftBAG3DV1,Bbox,GIS2BIM_NL.NLPDOKxPathOpenGISPosList2,GIS2BIM_NL.xPathStrings3DBag,-Rdx,-Rdy,1000,3,3)
	BAG3DSolids = GIS2BIM_FreeCAD.Buildings3D(curves3DBAG,heightData3DBAG)
	GIS_3D.addObjects(BAG3DSolids)

# Import Aerialphoto in view
if Aerialphoto2D is True:
	GIS_Raster = App.activeDocument().addObject("App::DocumentObjectGroup", "GIS Raster")	
	GIS2BIM.WMSRequest(GIS2BIM_NL.NLPDOKLuchtfoto2019,Bbox,fileLocationWMS)
	ImageAerialPhoto = GIS2BIM_FreeCAD.ImportImage(fileLocationWMS,width,height,1000,"luchtfoto2019")
	GIS_Raster.addObject(App.activeDocument().getObject("luchtfoto2019"))

#Create Textdata Cadastral Parcels
if GIS2DAnnotation is True:
	GIS_Annotation = App.activeDocument().addObject("App::DocumentObjectGroup", "GIS Annotation")	
	textDataCadastralParcels = GIS2BIM.DataFromWFS(GIS2BIM_NL.NLPDOKCadastreCadastralParcelsNummeraanduiding,Bbox,GIS2BIM_NL.NLPDOKxPathOpenGISPos,GIS2BIM_NL.xPathStringsCadastreTextAngle,-Rdx,-Rdy,1000,3,2)
	textDataOpenbareRuimtenaam = GIS2BIM.DataFromWFS(GIS2BIM_NL.NLPDOKCadastreOpenbareruimtenaam,Bbox,GIS2BIM_NL.NLPDOKxPathOpenGISPos,GIS2BIM_NL.xPathStringsCadastreTextAngle,-Rdx,-Rdy,1000,3,2)
	placeTextFreeCAD1 = GIS2BIM_FreeCAD.PlaceText(textDataCadastralParcels,500,0)
	placeTextFreeCAD2 = GIS2BIM_FreeCAD.PlaceText(textDataOpenbareRuimtenaam,2000,1)
	GIS_Annotation.addObjects(placeTextFreeCAD1)
	GIS_Annotation.addObjects(placeTextFreeCAD2)

#Create Ruimtelijke plannen outline 2D
if Bestemmingsplan is True:
	GIS_2D_Ruimtelijke_Plannen = App.activeDocument().addObject("App::DocumentObjectGroup", "GIS 2D Ruimtelijke Plannen")	
	RuimtelijkePlannenBouwvlakCurves = GIS2BIM_FreeCAD.CurvesFromWFS(GIS2BIM_NL.NLRuimtelijkeplannenBouwvlak,Bbox,GIS2BIM_NL.NLPDOKxPathOpenGISposList,-Rdx,-Rdy,1000,3,2,False,u"Solid",(0.0,0.0,1.0))
	GIS_2D_Ruimtelijke_Plannen.addObjects(RuimtelijkePlannenBouwvlakCurves)
	
FreeCAD.ActiveDocument.recompute()
