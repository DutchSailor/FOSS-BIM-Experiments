#BAG 3D V2 
import sys
sys.path.append("C:/Users/mikev/Documents/GitHub/FOSS-BIM-Experiments/GIS2BIM/PyPackages")
sys.path.append("C:/Users/mikev/Documents/GitHub/FOSS-BIM-Experiments/GIS2BIM")

import importlib
from PyPackages import GIS2BIM
from PyPackages import GIS2BIM_NL
from PyPackages import GIS2BIM_FreeCAD
from PyPackages import GIS2BIM_CRS 
from PyPackages import GIS2BIM_GUI
importlib.reload(GIS2BIM_NL)
importlib.reload(GIS2BIM_FreeCAD)

import json

sitename = "GIS-Sitedata"

tempFolderName = "GIStemp/BAG3D/"
tempFolder = GIS2BIM_FreeCAD.CreateTempFolder(tempFolderName)

X = str(GIS2BIM_FreeCAD.ArchSiteCreateCheck(sitename).CRS_x)
Y = str(GIS2BIM_FreeCAD.ArchSiteCreateCheck(sitename).CRS_y)	
dx = -float(X) * 1000
dy = -float(Y) * 1000

bboxWidthStart = str(GIS2BIM_FreeCAD.ArchSiteCreateCheck(sitename).BoundingboxWidth)
bboxHeightStart = str(GIS2BIM_FreeCAD.ArchSiteCreateCheck(sitename).BoundingboxHeight)

bboxString = GIS2BIM.CreateBoundingBox(float(GIS2BIM_FreeCAD.ArchSiteCreateCheck(sitename).CRS_x),float(GIS2BIM_FreeCAD.ArchSiteCreateCheck(sitename).CRS_y),float(bboxWidthStart),float(bboxHeightStart),0)

jsonFile = "C:\Users\mikev\Desktop\TEMP\GIStemp\BAG3D\3dbag_v210908_fd2cee53_3432.json"

def CityJSONImport(jsonFile,dX,dY,LODnumber,bboxWidth,bboxHeight):
	#Import CityJSON File, jsonfilename, dx and dy in string/meters. Proof of Concept, very buggy and incomplete.
	layer = GIS2BIM_FreeCAD.CreateLayer("CityJSON")	
	data = json.load(open(jsonFile,))
	vert = data['vertices']
	cityobj = data['CityObjects']
	translate = data['transform']['translate']
	scaleX = data['transform']['scale'][0]
	scaleY = data['transform']['scale'][1]
	scaleZ = data['transform']['scale'][2]
	translatex = (translate[0] -float(dX))/scaleX
	translatey = (translate[1] -float(dY))/scaleY
	translatez = -translate[2]/scaleZ
	geographicalExtent = data['metadata']['geographicalExtent']
	
	meshes = []
	for i in cityobj:
		objName = i
		for j in data['CityObjects'][objName]['geometry'][2]['boundaries']:	
			facets = []
			for k in j:
				coord = (str(vert[k[0][0]][0]+translatex), str(vert[k[0][0]][1]+translatey))					
				if checkIfCoordIsInsideBoundingBox(coord,-500*float(bboxWidth),-500*float(bboxHeight),500*float(bboxWidth),500*float(bboxHeight)):				
					facets.append(((vert[k[0][0]][0]+translatex, vert[k[0][0]][1]+translatey, vert[k[0][0]][2]+translatez),(vert[k[0][1]][0]+translatex, vert[k[0][1]][1]+translatey, vert[k[0][1]][2]+translatez),(vert[k[0][2]][0]+translatex, vert[k[0][2]][1]+translatey, vert[k[0][2]][2]+translatez)))
				else: pass
			m = Mesh.Mesh(facets)
			f = FreeCAD.activeDocument().addObject("Mesh::Feature", objName)
			f.Mesh = m
			meshes.append(f)
			FreeCAD.activeDocument().getObject("CityJSON").addObject(f)
	return meshes

Import = CityJSONImport(jsonFile,dx,dy,1,bboxWidthStart,bboxHeightStart)

FreeCAD.ActiveDocument.recompute()

#Download Basisvoorziening

#https://download.pdok.nl/kadaster/basisvoorziening-3d/v1_0/2019/volledig/38dn1_2019_volledig.zip
