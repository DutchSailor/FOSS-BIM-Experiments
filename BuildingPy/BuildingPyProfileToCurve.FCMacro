#FreeCAD imports
import Draft
import Part
import Arch
import FreeCAD
from FreeCAD import Vector

#General imports
import sys, os, math
from pathlib import Path
import json
import urllib.request
import importlib

package_root_directory = "C:/Users/mikev/Documents/GitHub/building.py/"
sys.path.append(str(package_root_directory))

#Building Py Imports
from objects.frame import *
from objects.steelshape import *

def polycurve2d_to_part_wire(poly_curve_2d: PolyCurve2D):
    PartCurves = []
    for i in poly_curve_2d.curves:
        if i.__class__.__name__ == "Arc2D":
            curve = Part.Arc(Vector(i.start.x,i.start.y,0),Vector(i.mid.x,i.mid.y,0),Vector(i.end.x,i.end.y,0))
            PartCurves.append(curve.toShape())
        elif i.__class__.__name__ == "Line2D":
            PartCurves.append(Part.makeLine(Vector(i.start.x,i.start.y,0),Vector(i.end.x,i.end.y,0)))
    aWire = Part.Wire(PartCurves)
    return aWire

def wire_to_solid(wire,height):
    p = Part.Face(wire)
    solid = p.extrude(FreeCAD.Vector(0, 0, height))
    sld = Part.show(solid)


test = profiledataToShape("HEA200").polycurve2d

wire_to_solid(polycurve2d_to_part_wire(test),1000)
